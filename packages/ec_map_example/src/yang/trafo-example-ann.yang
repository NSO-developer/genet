module trafo-example-ann {
  namespace "http://cisco.com/ns/genet/examples/transforms/ann";
  prefix ex-ann;

  import tailf-common {
    prefix tailf;
  }
  import trafo-example {
    prefix ex;
  }

  tailf:annotate /ex:example-domain {
    tailf:callpoint "ec_genet" { tailf:transform true; }
  }
}
