module trafo-example-device {
  namespace "http://cisco.com/ns/genet/examples/transforms/device";
  prefix exdev;

  import ietf-inet-types { prefix inet; }
  
  container example-device {
    container direct {
      container leaf-string {
        leaf k {
          type string;
        }
      }
      container leaf-uint {
        leaf k {
          type uint32;
          default 14;
        }
      }
      container leaf-ip {
        leaf k {
          type inet:ip-address;
        }
      }
      container leaf-empty {
        leaf k {
          type empty;
        }
      }
      container container {
      }
      container container-presence {
        presence 
          "Creation/deletion of this p-container is an act of
           configuration.";
      }
      container choice {
        choice k {
          case n {
            leaf o { type string; }
            leaf p { type uint32; }
          }
          leaf q { type empty; }
          container r {
            leaf s { type inet:ip-address; }
            leaf t { type boolean; }
          }
        }
      }
      container choice-in-choice {
        choice k {
          case l {
            choice m {
              case n {
                leaf o { type string; }
                leaf p { type uint32; }
              }
              leaf q { type empty; }
            }
          }
          container r {
            leaf s { type inet:ip-address; }
            leaf t { type boolean; }
          }
        }
      }
      container leaf-list {
        leaf-list k {
          type int8;
        }
      }
      container list {
        list k {
          key l;
          leaf l {
            type string;
          }
        }
      }
    }

    container types {
      container integers {
        container int32 {
          leaf k { type int32; }
        }
        container uint32 {
          leaf k { type uint32; }
        }
        container uint8 {
          leaf k { type uint8; }
        }
      }
      container string {
        leaf k { type string; }
      }
      container union {
        leaf k {
          type union {
            type uint8 { range '0..100'; }
            type int32 { range '1000..2000'; }
            type string;
            type boolean;
          }
        }
      }
      container ip-address {
        leaf k {
          type inet:ip-address;
        }
      }
      container ipv6-prefix {
        leaf k {
          type inet:ipv6-prefix;
        }
      }
      container leaf-list {
        leaf-list k {
          type uint8;
        }
      }
    }

    container value {
      container constant { 
      }
      container range {
        container expanding {
          leaf k {
            type uint8 {
              range "0..3";
            }
          }
        }
        container contracting {
          leaf k {
            type uint8 {
              range "0..2";
            }
          }
        }
      }
      container scaling {
        container expanding {
          leaf k {
            type uint8 {
              range "0..255";
            }
          }
        }
        container contracting {
          leaf k {
            type uint8 {
              range "0..100";
            }
          }
        }
      }
      container precision {
        leaf k {
          type uint8 {
            range '0..10';
          }
        }
      }
      container offset {
        leaf k {
          type uint8 {
            range '1..8';
          }
        }
      }
      container composition {
        leaf k {
          type int32;
        }
      }
      container types {
        container integers {
          leaf k {
            type int32 {
              range 0..1000;
            }
          }
        }
        container lists {
          list k {
            key l;
            leaf l {
              type int32 {
                range "0..255";
              }
            }
          }
        }
        container leaf-list {
          leaf-list k {
            type uint8 {
              range 0..100;
            }
          }
        }
      }
      container representation {
        container string-to-binary {
          leaf k {
            type binary {
              length 6;
            }
          }
        }
        container integer-to-string {
          leaf k {
            type string {
              pattern "0|1000|[1-9][0-9]{0,2}";
            }
          }
        }
        container identityref {
          leaf k {
            type string {
              pattern 'id1|id2|id3';
            }
          }
        }
      }
      container enumerations {
        leaf k {
          type enumeration {
            enum alert;
            enum debugging;
            enum info;
            enum trace;
          }
        }
      }
    }
    container existence { 
      container constant {
        // nothing here
      }
      container sentinel {
        container sentinel-hl {
          leaf k {
            type uint8 {
              range 1..100;
            }
          }
        }
        container sentinel-ll {
          leaf k {
            type string;
            default "";
          }
        }
      }
      container boolean {
        container boolean-to-existence {
          leaf k {
            type empty;
          }
        }
        container existence-to-enum {
          leaf k {
            type enumeration {
              enum notexists;
              enum exists;
            }
            default notexists;
          }
        }
      }
      container case-map {
        leaf k {
          type enumeration {
            enum case-b;
            enum case-e;
          }
        }
        leaf l {
          type string;
        }
        leaf m {
          type int32;
        }
      }
    }
    container address {
      container constant {
        leaf k {
          type uint32;
        }
      }
      container dynamic {
        container choice {
          choice c {
            leaf k { type string; }
            leaf l { type string; }
          }
        }
        container lists {
          list l1 {
            key a;
            leaf a {
              type int32;
            }
          }
          list l2 {
            key a;
            leaf a {
              type int32;
            }
          }
          list l3 {
            key a;
            leaf a {
              type int32;
            }
          }
        }
      }
      container key-constant {
        list k {
          key l;
          leaf l {
            type string;
          }
        }
      }
      container key-offset {
        list l {
          key k;
          leaf k {
            type int32 {
              range "1..8";
            }
          }
        }
      }
      container key-container {
        list k {
          key l;
          leaf l {
            type enumeration {
              enum c1;
              enum c2;
            }
          }
          leaf m {
            type string;
          }
        }
      }
      container lookup-table {
        list k {
          key l;
          leaf l {
            type uint32;
          }
          leaf m {
            type string;
          }
        }
      }
    }
    container structure {
      container leafs {
        container one-to-multiple-copies {
          leaf k {
            type string;
          }
          leaf l {
            type string;
          }
        }
        container one-to-multiple-parts {
          leaf k {
            type inet:ipv4-address;
          }
          leaf l {
            type inet:ipv4-address;
          }
        }
        container many-to-one {
          leaf k {
            type string {
              pattern '[1-9][0-9]{0,2}:[1-9][0-9]{0,2}';
            }
          }
        }
      }
      container lists {
        container split-by-cols {
          list k {
            key m;
            leaf m { type uint32; }
            leaf n { type string; }
          }
          list l {
            key m;
            leaf m { type uint32; }
            leaf o { type inet:ip-address; }
          }
        }
        container split-by-rows {
          container union {
            list ipv4 {
              key m;
              leaf m { 
                type enumeration {
                  enum ssh;
                  enum apache;
                  enum docker;
                }
              }
              leaf n { type string; }
            }
            list ipv6 {
              key m;
              leaf m { 
                type enumeration {
                  enum ssh;
                  enum apache;
                  enum docker;
                }
              }
              leaf n { type string; }
            }
          }
          container join {
            list ipv4 {
              key m;
              leaf m { 
                type enumeration {
                  enum ssh;
                  enum apache;
                  enum docker;
                }
              }
              leaf n { type string; }
            }
            list ipv6 {
              key m;
              leaf m { 
                type enumeration {
                  enum ssh;
                  enum apache;
                  enum docker;
                }
              }
              leaf n { type string; }
            }
          }
        }
        container sequencing {
          list k {
            key l;
            leaf l {
              type string {
                pattern "0|[1-9][0-9]{0,2}";
              }
            }
            leaf m {
              type string;
            }
          }
        }
      }
      container nested-lists {
        container nested-list-to-flat {
          list k {
            key "l m";
            leaf l { type uint32; }
            leaf m { type string; }
            leaf n { type boolean; }
          }
        }
        container flat-list-to-nested {
          list k {
            key l;
            leaf l { type inet:ip-address; }
            list m {
              key n;
              leaf n { type string; }
              leaf o { type uint8; }
            }
          }
        }
      }
      container list-to-leaf-list {
        leaf-list k { type uint32; }
      }
    }
    container nesting {
      container address-value {
        choice k {
          leaf l {
            type string;
          }
          leaf m {
            type string;
          }
        }
      }
      container existence-address {
        leaf k {
          type string {
            pattern "[be][01]";
          }
        }
      }
    }
  }
}
